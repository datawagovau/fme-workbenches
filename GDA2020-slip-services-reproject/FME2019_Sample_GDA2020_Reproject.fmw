FME workspace FME2019_Sample_GDA2020_Reproject.fmw

Parameters:
- SourceDataset_ARCGISFEATURES = https://services.slip.wa.gov.au/public/rest/services/SLIP_Public_Services/Property_and_Planning/MapServer   # Host
- Output_Destination =   # File Geodatabase

Readers:
- ARCGISFEATURES_1: ARCGISFEATURES from $(SourceDataset_ARCGISFEATURES)

Writers:
- GEODATABASE_FILE_1: GEODATABASE_FILE to $(Output_Destination)

Note: Input can be either current EPSG:3857@GDA94 or future EPSG:7844
Geodetic Survey Marks (Point) (LGATE-076) (reader ARCGISFEATURES_1)
    attributes: objectid OID, point_number Integer, point_type String(1), geodetic_point_name String(25), stamped_name_on_point String(10), latest_status_description String(35), latest_status_date Date, cadastral_connection String(1), horiz_datum String(5), latitude_dd Double, longitude_dd Double, projection String(5), easting Double, northing Double, zone SmallInteger, horizontal_circular_error Double, horiz_method String(35), horiz_accuracy String(6), vert_datum String(5), reduced_level Double, vert_accuracy String(10), vertical_method String(35), url String(200), render_value String(4), filter_value Integer, point_type_desc String(10), cadastral_connection_desc String(15), station_summary_link String(150)
    -> SLIP_Reproject
SLIP_Reproject
    Output_3857 -> Geodetic_Survey_Marks__Point___LGATE_076_ (writer GEODATABASE_FILE_1)
Note: Output as EPSG:3857@GDA94
Geodetic_Survey_Marks__Point___LGATE_076_ (writer GEODATABASE_FILE_1)
    attributes: objectid integer, point_number integer, point_type char(1), geodetic_point_name char(25), stamped_name_on_point char(10), latest_status_description char(35), latest_status_date date, cadastral_connection char(1), horiz_datum char(5), latitude_dd double, longitude_dd double, projection char(5), easting double, northing double, zone smallint, horizontal_circular_error double, horiz_method char(35), horiz_accuracy char(6), vert_datum char(5), reduced_level double, vert_accuracy char(10), vertical_method char(35), url char(200), render_value char(4), filter_value integer, point_type_desc char(10), cadastral_connection_desc char(15), station_summary_link char(150)

FME custom transformer SLIP_Reproject

Note: Double hop required if wanting to go to EPSG:3857@GDA94
Input (input)
    -> CoordinateSystemExtractor
Note: Reads the Coordinate System and creates _coordsys attribute: / Current = SPHERICAL MERCATOR / Future = GDA2020
CoordinateSystemExtractor
    CRDSYS_ATTR = _coordsys
    -> Tester
Note: Tests for _coordsys for SPHERICAL MERCATOR (EPSG:3857)
Tester
    BOOL_OP = OR
    COMPOSITE_TEST = 1
    TEST_CLAUSE = CASE_INSENSITIVE_TEST @Value(_coordsys) = SPHERICAL_MERCATOR
    TEST_MODE = CASE_INSENSITIVE_TEST
    PASSED -> AttributeRemover
    FAILED -> CsmapReprojector
Note: Reprojects from GDA2020 to GDA94
CsmapReprojector
    DEST = LL-GDA94
    INTERPOLATION_TYPE_NAME = Nearest Neighbor
    RASTER_CELL_SIZE = Preserve Cells
    RASTER_TOLERANCE = 0.0
    SOURCE = LL-GDA2020_FME
    TRANSFORMATION = GDA94_to_GDA2020_conformal_and_distortion_NTv2_Grid_FME (Reversed)
    VERTICAL_HANDLING = Ignore heights and leave them unchanged
    REPROJECTED -> CsmapReprojector_2
Note: Reprojects from GDA94 to SPHERICAL MERCATOR
CsmapReprojector_2
    DEST = SPHERICAL_MERCATOR
    INTERPOLATION_TYPE_NAME = Nearest Neighbor
    RASTER_CELL_SIZE = Preserve Cells
    RASTER_TOLERANCE = 0.0
    SOURCE = LL-GDA94
    VERTICAL_HANDLING = Ignore heights and leave them unchanged
    REPROJECTED -> AttributeRemover
Note: Removes the _coordsys attribute
AttributeRemover
    REMOVE_ATTRS = _coordsys
    -> Output_3857 (output)
Output_3857 (output)
