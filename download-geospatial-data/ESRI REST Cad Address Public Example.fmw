FME workspace ESRI REST Cad Address Public Example.fmw

Parameters:
- SourceDataset_ARCGISFEATURES = https://services.slip.wa.gov.au/public/rest/services/SLIP_Public_Services/Property_and_Planning_WFS/MapServer   # Host
- SourceDataset_ARCGISFEATURES_7 = https://services.slip.wa.gov.au/public/rest/services/SLIP_Public_Services/Property_and_Planning_WFS/MapServer   # Host
- SourceDataset_ARCGISFEATURES_6 = https://services.slip.wa.gov.au/public/rest/services/SLIP_Public_Services/Property_and_Planning_WFS/MapServer   # Host

Readers:
- ARCGISFEATURES_1: ARCGISFEATURES from $(SourceDataset_ARCGISFEATURES)
- ARCGISFEATURES_3: ARCGISFEATURES from $(SourceDataset_ARCGISFEATURES_7)
- ARCGISFEATURES_4: ARCGISFEATURES from $(SourceDataset_ARCGISFEATURES_6) in EPSG:3857

Note: Download features where the 'Locality' field is 'Perth' / Reader Parameters - / - Features Per Request: Defaults to 1,000. May be set as high as the service will allow - typically 100,000. / Feature Type Format Parameters - / - WHERE Clause: PERTH
Cadastre Address (LGATE-002) (reader ARCGISFEATURES_1) [off]
    attributes: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
Note: Download features within 1km of Central Perth / Reader Parameters - / - Features Per Request: Defaults to 1,000. May be set as high as the service will allow - typically 100,000. / Feature Type Format Parameters - / - Input Geometry: X,Y (In the coordinate system of the dataset - usually Web Mercator.) / - Input Geometry Type: Point / - Spatial Relationship: Contains / - Distance: 1000 / - Units: Metres / NB: Envelope, Polyline, Polygon, and MultiPoint are also accepted for 'Input Geometry Type'. 'Input Geometry' must always be formatted as ESRI JSON.
Cadastre Address (LGATE-002) (reader ARCGISFEATURES_3)
    attributes: oid esriFieldTypeOID, ogc_fid esriFieldTypeInteger, land_id__number esriFieldTypeInteger, usage_code esriFieldTypeInteger, view_scale esriFieldTypeString(255), number_from_prefix esriFieldTypeString(255), number_from esriFieldTypeInteger, number_from_suffix esriFieldTypeString(255), number_type_label esriFieldTypeString(255), number_to_prefix esriFieldTypeString(255), number_to esriFieldTypeInteger, number_to_suffix esriFieldTypeString(255), road_name esriFieldTypeString(255), road_type esriFieldTypeString(255), road_direction esriFieldTypeString(255), locality_name esriFieldTypeString(255), row_id esriFieldTypeInteger, usage_description esriFieldTypeString(255), cad_eas esriFieldTypeString(255)
    -> Inspector
Inspector
Note: Download features within a given Bounding Box / Reader Parameters - / - Features Per Request: Defaults to 1,000. May be set as high as the service will allow - typically 100,000. / - Search Envelope: MINX, MINY, MAXX, MAXY / - Search Envelope: Coordinate System / - Coordinate System (MUST be set if the Search Envelope CRS is set.)
Cadastre Address (LGATE-002) (reader ARCGISFEATURES_4) [off]
    attributes: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
