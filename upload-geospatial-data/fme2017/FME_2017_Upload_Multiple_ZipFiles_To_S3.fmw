FME workspace FME_2017_Upload_Multiple_ZipFiles_To_S3.fmw

Parameters:
- AWS_ACCESS_KEY =   # Enter My AWS Access Key
- AWS_SECRET =   # Enter My AWS Secret Access Key
- ZIP_FOLDER =   # Enter Folder Containing Zip Files to Upload to s3
- S3_BUCKET = lg-slip-selfservice-data-prod/data-load/1   # Enter in your S3 bucket

Readers:
- PATH_1: PATH from $(ZIP_FOLDER)

Note: This FME Workbench can be used to automatically load multiple *.zip located in a single folder to AWS S3 / Instructions / 1)Log into the SLIP Data Upload Tool (https://selfservice.slip.wa.gov.au/) / 2)Navigate to the Upload Tab of an exsiting dataset to locate the AWS Access Key, AWS Access Secret and 3 Bucket Folder. / 3)Enter these values into the FME Published Parameters / 4)Enter the folder containing all the zip files to upload into slip. / 5)Run Workbench
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> S3Uploader
S3Uploader
    S3_DATA_FILE = @Value(path_windows)
    S3_REQUEST_HEADER_LIST_ATTR = _headers
    S3_BUCKET_NAME = $(S3_BUCKET)
    AWS_SECRET_KEY = $(AWS_SECRET)
    AWS_ACCESS_KEY = $(AWS_ACCESS_KEY)
    S3_CANNED_ACL = Private
    S3_OBJECT_KEY = @Value(path_filename)
    S3_AWS_REGION = Asia Pacific, Sydney (ap-southeast-2)
    S3_URI_ATTRIBUTE = _s3_object_uri
    S3_UPLOAD_ENCRYPTION = None
    S3_FILE_OR_DATA = File
    S3_ACCELERATION = No
